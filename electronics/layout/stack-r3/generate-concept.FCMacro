import FreeCAD as App, Part, Import, FreeCADGui as Gui
from pivy import coin
from pathlib import Path
import json
out=Path('D:/UserData/ARIA/current-task/outputs/SolidWorks-layout')
out.mkdir(parents=True,exist_ok=True)
records=[]
def build(name,explode):
 doc=App.newDocument(name); objects=[]
 def block(label,x,y,z,w,h,t,color):
  obj=doc.addObject('PartDesign::Feature',label.replace(' ','_'));obj.Label=label
  obj.Shape=Part.makeBox(w,h,t,App.Vector(x,y,z));obj.ViewObject.ShapeColor=color;objects.append(obj)
  records.append(dict(document=name,label=label,x=x,y=y,z=z,w=w,h=h,t=t))
  return obj
 green=(0.12,0.48,0.33);blue=(0.16,0.42,0.76);black=(0.17,0.19,0.22);orange=(0.88,0.51,0.16);purple=(0.53,0.31,0.69)
 a=0;b=30+explode;c=60+2*explode
 block('BASE_70x100_CONFIRMED_OUTLINE_ONLY',0,0,a,70,100,1.6,green)
 for x in (5,38):
  block('DRIVER_ENVELOPE_'+str(x),x,5,a+4,26,21.5,1.6,black)
  block('DRIVER_COMPONENT_ALLOWANCE_'+str(x),x+3,9,a+5.6,20,12,10,black)
 block('POLOLU_PLACEHOLDER',5,37,4,22,42,14,orange)
 block('IP2368_PLACEHOLDER',34,36,4,31,25,12,orange)
 block('INA260_PLACEHOLDER',35,70,4,25,25,10,blue)
 block('LOGIC_CARRIER_PLACEHOLDER',0,0,b,70,94,1.6,green)
 block('ESP_SOCKET_ENVELOPE',3,53,b+2,29,62,5,black)
 block('ESP_YD_NOMINAL_BOARD',3,56.5,b+7,27.94,63.5,1.6,black)
 block('ESP_MODULE_SHIELD_PLACEHOLDER',6,88,b+8.6,22,23,3,(0.7,0.72,0.74))
 block('ESP_ANTENNA_CLEAR_ALL_LAYERS',3,114,b+8.6,28,6,1,(0.85,0.66,0.24))
 for x in (4,18):block('ESP_USB_ACCESS_'+str(x),x,53,b+8.6,12,8,4,(0.7,0.72,0.74))
 for y in (12,43):
  block('AMP_PLACEHOLDER_'+str(y),43,y,b+4,20,24,5,purple)
 # isolated edge terminal banks, no electrical links
 for i,(label,color) in enumerate([('GND',black),('VBAT',orange),('5V',(0.9,0.22,0.2)),('3V3_PI',blue),('3V3_ESP',green)]):
  block('ISOLATED_POWER_BANK_'+label,3+i*13,1,b+3,10,8,7,color)
 block('PI_SENSOR_CONNECTOR_PLACEHOLDER',43,78,b+4,22,10,8,blue)
 block('PI5_OUTLINE_56x85_NOMINAL',7,0,c,56,85,1.6,green)
 block('PI_PORT_ENVELOPE_PLACEHOLDER',9,1,c+1.6,51,20,16,(0.68,0.7,0.72))
 block('COOLER_ENVELOPE_PLACEHOLDER',18,31,c+1.6,33,38,15,(0.47,0.5,0.54))
 fan=doc.addObject('PartDesign::Feature','FAN_PLACEHOLDER'); fan.Shape=Part.makeCylinder(12,3,App.Vector(34.5,50,c+16.6));fan.ViewObject.ShapeColor=black;objects.append(fan)
 if not explode:
  for x,y in ((2,3),(67,3),(2,88),(67,88)):
   for zz,hh in ((1.6,28.4),(31.6,28.4)):
    # rear posts stop before Pi since no mount holes have been validated
    if y==88 and zz>10:continue
    ob=doc.addObject('PartDesign::Feature','STANDOFF_CONCEPT');ob.Shape=Part.makeCylinder(1.7,hh,App.Vector(x,y,zz));ob.ViewObject.ShapeColor=(0.85,0.84,0.73);objects.append(ob)
 doc.recompute();Gui.activeDocument().activeView().viewAxonometric();Gui.activeDocument().activeView().fitAll()
 doc.saveAs(str(out/(name+'.FCStd')))
 Import.export(objects,str(out/(name+'.step')))
 Gui.Selection.clearSelection()
 for item in objects: item.ViewObject.LineColor=(0.22,0.25,0.28)
 Gui.updateGui()
 Gui.activeDocument().activeView().fitAll()
 camera=Gui.activeDocument().activeView().getCameraNode()
 camera.height.setValue(camera.height.getValue()*1.2)
 Gui.updateGui()
 assert all(item.Shape.isValid() for item in objects)
 Gui.activeDocument().activeView().saveImage(str(out/(name+'.png')),1500,1100,'White')
 return doc
try:
 build('ARIA_STACK_R3_ASSEMBLED_CONCEPT',0)
 build('ARIA_STACK_R3_EXPLODED_CONCEPT',32)
 (out/'placement-concept.json').write_text(json.dumps(records,indent=2),encoding='utf-8')
 (out/'generation-error.txt').unlink(missing_ok=True)
 (out/'generation-done.txt').write_text('Two concept documents exported. Placeholder bodies, not verified component models. No released mounting holes.',encoding='utf-8')
except Exception:
 import traceback
 (out/'generation-error.txt').write_text(traceback.format_exc(),encoding='utf-8')
for name in list(App.listDocuments()): App.closeDocument(name)
Gui.getMainWindow().close()
